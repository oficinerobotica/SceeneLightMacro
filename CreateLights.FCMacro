import FreeCAD as FC
import FreeCADGui as FCGui
import os
import sys

# Add macro directory to Python path
macro_dir = os.path.dirname(__file__)
sys.path.insert(0, macro_dir)

try:
    from Lights import directional_light, spot_light, point_light
except ImportError as e:
    FC.Console.PrintError(f"Failed to import Lights module: {e}\n")
    raise


# Step 1: Create or get the active document
doc = FC.ActiveDocument

# Step 2: Create an object group named "Scene"
scene_group = doc.addObject("App::DocumentObjectGroup", "Scene")
FC.Console.PrintMessage("Created group: 'Scene'\n")

# Step 3: Create an App::Part object named "Lights"
lights_part = doc.addObject("App::Part", "Lights")
FC.Console.PrintMessage("Created App::Part: 'Lights'\n")
lights_part.ViewObject.Visibility = False  # Make visible to see lights

#Step 4: Add the "Lights" App::Part to the "Scene" group
scene_group.addObject(lights_part)
FC.Console.PrintMessage("Added 'Lights' to 'Scene'\n")

# Constants
LIGHT_COLOR = (255, 179, 85)
LIGHT_INTENSITY = 0.5

def create_directional_light(name, horizontal_rot, vertical_rot):
   """  Create a directional light and set its properties. """ 
   lightDirectional = directional_light.createDirectionalLight()
   if lightDirectional:
        lightDirectional.HorizontalRotation = horizontal_rot
        lightDirectional.VerticalRotation = vertical_rot
        lightDirectional.Intensity = LIGHT_INTENSITY
        lightDirectional.Color = LIGHT_COLOR
        return lightDirectional

def create_point_light(name):
     """Create a point light and set its properties."""
     lightPoint = point_light.createPointLight()
     if lightPoint:
        lightPoint.Intensity = LIGHT_INTENSITY
        lightPoint.Color = LIGHT_COLOR
        return lightPoint 


def create_spot_light(name):
     """Create a spot light and set its properties."""
     lightSpot = spot_light.createSpotLight()
     if lightSpot:
        lightSpot.Intensity = LIGHT_INTENSITY
        lightSpot.Color = LIGHT_COLOR
        return lightSpot 



Light1 = create_directional_light('DirectionalLight', -90, 60)
if Light1:
    lights_part.addObject(Light1)

Light2 = create_directional_light('DirectionalLight', 120, 45)
if Light2:
    lights_part.addObject(Light2)

Light3 = create_point_light('PointLight')
if Light3:
    lights_part.addObject(Light3)

Light4 = create_spot_light('SpotLight')
if Light4:
    lights_part.addObject(Light4) 
    

# Recompute the document
FC.ActiveDocument.recompute()
FCGui.SendMsgToActiveView("ViewFit")  # Zoom to fit
